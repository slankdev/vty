module coreswitch {
  yang-version "1";

  namespace "http://coreswitch.io/";
  prefix "coreswitch";

  import ietf-inet-types {
    prefix inet;
  }

  import coreswitch-ntp {
    prefix ntp;
  }

  import coreswitch-ext {
    prefix ext;
  }

  container vlans {
    list vlan {
      key "id";
      leaf id {
        type uint16 {
          range 1..4096;
        }
      }
    }
  }

  container interfaces {
    list interface {
      key "name";
      leaf name {
        type string;
      }
      leaf vrf {
        type string;
      }
			leaf mirror {
				type string;
			}
      leaf descriptionx {
        type string;
      }
      leaf vlan {
        type uint16 {
          range 1..4096;
        }
      }
      list vlans {
        key "vlan-id";
        leaf vlan-id {
          type uint16 {
            range 1..4096;
          }
        }
      }
    }
  }

  container routing-options {
    ext:help "routing-option help";
    leaf router-id {
      type inet:ipv4-address;
    }
    container ipv4 {
      list route {
        key "prefix";
        leaf prefix {
          type inet:ipv4-prefix;
        }
        list nexthop {
          key "address";
          leaf "address" {
            type inet:ipv4-address;
            description "Nexthop of the route";
          }
        }
        list interface {
          key "ifname";
          leaf "ifname" {
            type string;
          }
        }
        leaf distance {
          type uint8;
          description "Distance of the route.";
        }
      }
      list route-srv6 {
        key "prefix";
        leaf prefix {
          type inet:ipv4-prefix;
        }
        list nexthop {
          key "address";
          leaf "address" {
            type inet:ipv4-address;
            description "Nexthop of the route";
          }
          list seg6 {
            key "mode";
            leaf mode {
              type enumeration {
                enum encap;
              }
            }
            leaf-list segments {
              type inet:ipv6-address;
            }
          }
        }
      }
    }
    container ipv6 {
      list route {
        key "prefix";
        leaf prefix {
          type inet:ipv6-prefix;
        }
        list nexthop {
          key "address";
          leaf "address" {
            type inet:ipv6-address;
          }
        }
      }
      list route-srv6 {
        key "prefix";
        leaf prefix {
          type inet:ipv6-prefix;
        }
        list nexthop {
          key "address";
          leaf "address" {
            type inet:ipv6-address;
          }
          list seg6 {
            key "mode";
            leaf mode {
              type enumeration {
                enum inline;
                enum encap;
              }
            }
            leaf-list segments {
              type inet:ipv6-address;
            }
          }
        }
      }
    }
  }

  container protocols {
    ext:help "Routing protocol configuration";
    uses quagga:protocols;
  }

  container policy {
    uses quagga:policy;
  }

  container system {
    description
      "System group configuration.";

    leaf hostname {
      type inet:domain-name;
      description
        "The name of the host.  This name can be a single domain
        label or the fully qualified domain name of the host.";
    }
    container ntp {
      uses "ntp:ntp";
    }
  }
}
